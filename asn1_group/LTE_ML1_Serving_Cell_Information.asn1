LTE-ML1-Serving-Cell-Information DEFINITIONS ::=BEGIN

LTE-ML1-Serving-Cell-Information-S-H ::=SEQUENCE
{
    version                      INTEGER (0..255),

    dl-bandwidth                 Dl-bandwidth,
    skip0                        BIT STRING(SIZE(4)),

    sfn                          INTEGER (0..65535),

    e-arfcn                      INTEGER (0..4294967295),

    pHICH-Resource               INTEGER (0..7),
    pHICH-Duration               INTEGER (0..3),
    pBCH-Decode-Result           INTEGER (0..3),
    physical-cell-id             INTEGER (0..511),

    pSS-Correlation              INTEGER (0..255),

    skip1                        OCTET STRING(SIZE(5)),

    sSS-Correlation              INTEGER (0..65535),

    skip2                        OCTET STRING(SIZE(2)),

    ref-time                     INTEGER(0..281474976710655),

    skip3                        OCTET STRING(SIZE(2)),

    mIB-payload                  INTEGER (0..4294967295),
    
    freq-Offset                  INTEGER (0..255),
    skip4                        BIT STRING(SIZE(7)),
    num-Antennas                 INTEGER (0..3),
    skip5                        BIT STRING(SIZE(15))
}

Dl-bandwidth ::=ENUMERATED
{
    unknown0                    (0),
    unknown1                    (1),
    unknown2                    (2),
    mhz-10                      (3),
    mhz-15                      (4),
    unknown5                    (5),
    unknown6                    (6),
    unknown7                    (7),
    unknown8                    (8)
}

END
