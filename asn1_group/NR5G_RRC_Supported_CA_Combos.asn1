NR5G-RRC-Supported-CA-Combos DEFINITIONS ::=BEGIN

-- S H --
NR5G-RRC-Supported-CA-Combos-S-H ::=SEQUENCE
{
    version                     INTEGER(0..4294967295),
    total-num-combos-from-rf    INTEGER(0..65535),
    starting-index              INTEGER(0..65535),
    num-combos                  INTEGER(0..65535),
    
    skip0                       BIT STRING(SIZE(7)),
    source                      Source
}
Source ::=ENUMERATED
{
    rf                          (0),
    unknown1                    (1)
}


-- Combo header -- 
NR5G-RRC-Supported-CA-Combos-Combo-H ::=SEQUENCE
{
    skip1                       BIT STRING(SIZE(3)),
    envelope-mode-pruned-out    Envelope-Mode-Pruned-Out,
    num-bands                   INTEGER(0..7),
    skip2                       BIT STRING(SIZE(1)),

    env-mask                    INTEGER(0..255),
    bc-id                       INTEGER(0..255),

    skip3                       BIT STRING(SIZE(7)),
    muting-state                Muting-State
}
Envelope-Mode-Pruned-Out ::=ENUMERATED
{
    false                       (0),
    true                        (1)
}
Muting-State ::=ENUMERATED
{
    exact-match                 (0),
    unknown1                    (1)
}

-- BW Class --
NR5G-RRC-Supported-CA-Combos-BW-Class ::=SEQUENCE
{
    band                        INTEGER(0..65535),

    skip4                       BIT STRING(SIZE(5)),
    dl-bw-class                 Dl-Bw-Class,
    tech                        Tech,

    skip5                       BIT STRING(SIZE(4)),
    dl-max-antennas-index       Dl-Max-Antennas-Index,

    skip6                       BIT STRING(SIZE(6)),
    ul-bw-class                 Ul-Bw-Class,
    ul-type                     Ul-Type,

    skip7                       BIT STRING(SIZE(6)),
    ul-max-antennas-index       Ul-Max-Antennas-Index,

    ul-qam-cap-index            INTEGER(0..255),

    skip8                       BIT STRING(SIZE(5)),
    srs-tx-switch-type          Srs-Tx-Switch-Type,


    skip9                       BIT STRING(SIZE(14)),
    max-scs                     Max-Scs
}
Dl-Bw-Class ::=ENUMERATED
{
    class-a                     (0),
    class-c                     (1)
}
Tech ::=ENUMERATED
{
    unknown0                    (0),
    unknown1                    (1),
    lte                         (2),
    nr                          (3)
}
Dl-Max-Antennas-Index ::=ENUMERATED
{
    unknown0                    (0),
    unknown1                    (1),
    antenna-2                   (2),
    antenna-4                   (3),
    unknown4                    (4),
    unknown5                    (5),
    unknown6                    (6),
    unknown7                    (7),
    antenna-4-4                 (8)
}
Ul-Bw-Class ::=ENUMERATED
{
    none                        (0),
    class-a                     (1)
}
Ul-Type ::=ENUMERATED
{
    unknown0                    (0),
    contiguous                  (1)
}
Ul-Max-Antennas-Index ::=ENUMERATED
{
    invalid                     (0),
    antenna-1                   (1),
    antenna-2                   (2)
}
Srs-Tx-Switch-Type ::=ENUMERATED
{
    unknown0                    (0),
    unsupported                 (1),
    unknown2                    (2),
    srs-t1-r2                   (3),
    unknown4                    (4),
    unknown5                    (5),
    srs-t2-r4                   (6)
}
Max-Scs ::=ENUMERATED
{
    unknown0                    (0),
    scs-15                      (1),
    scs-30                      (2)
}
END
