NR5G-RLC-DL-Status-PDU DEFINITIONS ::=BEGIN
NR5G-RLC-DL-Status-PDU-S-H ::=SEQUENCE
{
    version                     INTEGER(0..4294967295),
    num-status-pdu              INTEGER(0..4294967295)
}

NR5G-RLC-DL-Status-PDU-PDU-H ::=SEQUENCE
{
    slot                        INTEGER(0..65535),
    frame                       INTEGER(0..65535),

    skip0                       OCTET STRING(SIZE(1)),
    sn-length-value             INTEGER(0..255),
    status-pdu-size             INTEGER(0..255),
    skip1                       OCTET STRING(SIZE(1))
}
END
