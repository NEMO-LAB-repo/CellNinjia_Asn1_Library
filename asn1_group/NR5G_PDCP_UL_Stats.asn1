NR5G-PDCP-UL-Stats DEFINITIONS ::= BEGIN

--S-H--
NR5G-PDCP-UL-Stats-S-H ::= SEQUENCE
{
    version                     INTEGER(0..4294967295),
    skip                        BIT STRING(SIZE(5)),
    reason                      Reason,

    cumulative-srb-bmask       INTEGER(0..7),
    num-rb-logged              INTEGER(0..31),

    configured-srb-bmask       INTEGER(0..255),
    skip1                      OCTET STRING(SIZE(1)),
    cumulative-drb-bmask       INTEGER(0..255),
    skip2                      OCTET STRING(SIZE(3)),
    configured-drb-bmask       INTEGER(0..255),
    skip3                      OCTET STRING(SIZE(7)),

    num-pdcp-control-pdus       INTEGER(0..4294967295),
    num-discard-packets       INTEGER(0..4294967295),
    num-discard-bytes         INTEGER(0..4294967295),
    skip4                     OCTET STRING(SIZE(4)),

    total-count               INTEGER(0..65535),
    count-low               INTEGER(0..255),
    count-high              INTEGER(0..255),
    count-empty             INTEGER(0..255),
    count-non-empty         INTEGER(0..255),
    skip5                   OCTET STRING(SIZE(34))
}
Reason ::=ENUMERATED
{
    unknown0                   (0),
    periodic1                   (1),
    rrc-recfgd1              (2),
    unknown3                   (3),
    rrc-release              (4)
}


-- Record --
NR5G-PDCP-UL-Stats-Record ::= SEQUENCE
{
    skip0                       BIT STRING(SIZE(6)),
    rb-id                       INTEGER(0..3),

    skip1                       OCTET STRING(SIZE(3)),
    current-pdcp-count-hfn       INTEGER(0..16383),
    current-pdcp-count-sn        INTEGER(0..262143),

    total-num-discard-packets       INTEGER(0..4294967295),
    skip2                     OCTET STRING(SIZE(4)),
    total-num-discard-bytes         INTEGER(0..4294967295),
    skip3                     OCTET STRING(SIZE(8)),
    current-num-wm-packets       INTEGER(0..65535),
    skip4                     OCTET STRING(SIZE(6)),
    num-rx-packets              INTEGER(0..4294967295),
    total-num-rx-bytes          INTEGER(0..4294967295),
    skip5                     OCTET STRING(SIZE(12)),
    current-num-wm-bytes       INTEGER(0..4294967295),
    skip6                     OCTET STRING(SIZE(12)),
    total-count               INTEGER(0..65535),
    count-low               INTEGER(0..255),
    count-high              INTEGER(0..255),
    count-empty             INTEGER(0..255),
    count-non-empty         INTEGER(0..255),
    skip7                   OCTET STRING(SIZE(2)),

    dne-bytes                   INTEGER(0..4294967295),
    high-wm-threshold-bytes       INTEGER(0..4294967295),
    low-wm-threshold-bytes        INTEGER(0..4294967295),
    skip8                     OCTET STRING(SIZE(5)),
    skip9                     BIT STRING(SIZE(6)),
    pdcp-flow-state           PDCP-Flow-State,
    skip10                    OCTET STRING(SIZE(30))
}
PDCP-Flow-State ::= ENUMERATED
{
    unknown0                   (0),
    enabled                   (1),
    suspended                (2)
}


END
