NR5G-NAS-Plain-Message-Container DEFINITIONS ::=BEGIN

NR5G-NAS-Plain-Message-Container-S-H ::=SEQUENCE
{
    version                     INTEGER(0..4294967295),
    relesase-version0           INTEGER (0..255),
    relesase-version1           INTEGER (0..255),
    relesase-version2           INTEGER (0..255)
}
END
