NR5G-RRC-Serving-Cell-Info DEFINITIONS ::=BEGIN

NR5G-RRC-Serving-Cell-Info-S-H ::=SEQUENCE
{
    version                     INTEGER(0..4294967295),
    physicall-cell-id           INTEGER(0..65535),
    dl-frequency                INTEGER(0..4294967295),
    ul-frequency                INTEGER(0..4294967295),
    dl-bandwidth                INTEGER(0..65535),
    ul-bandwidth                INTEGER(0..65535),

    cell-id                     OCTET STRING(SIZE(8)),
    selected-plmn-mcc           INTEGER(0..65535),
    num-mnc-digits              INTEGER(0..255),
    selected-plmn-mnc           INTEGER(0..255),
    allowed-access              INTEGER(0..255),

    skip0                       INTEGER(0..255),
    tac                         INTEGER(0..4294967295),
    freq-band-indicator         INTEGER(0..65535)
}

END
