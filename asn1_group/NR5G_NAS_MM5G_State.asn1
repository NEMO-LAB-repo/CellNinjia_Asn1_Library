NR5G-NAS-MM5G-State DEFINITIONS ::= BEGIN

-- Content -- 
NR5G-NAS-MM5G-State-Content ::= SEQUENCE
{
    version                 INTEGER (0..4294967295),
    skip0                   BIT STRING (SIZE(5)),
    mm5g-state              MM5G-State,
    skip1                   OCTET STRING (SIZE(2)),
    plmn-id                 PLMN-Id,
    skip2                   OCTET STRING (SIZE(1)),
    guti                 GUTI,
    skip3                   OCTET STRING (SIZE(1)),
    nr5g-tac                OCTET STRING (SIZE(3))
}
MM5G-State ::=ENUMERATED
{
    unknown (0),
    deregistered (1),
    registered-initiated (2),
    registered (3),
    service-request-initiated (4),
    deregistered-initiated   (5),
    unknown6 (6),
    unknown7 (7)
}
PLMN-Id ::= SEQUENCE
{
    identity                OCTET STRING (SIZE(3))
}
GUTI ::=SEQUENCE
{
    identity                OCTET STRING (SIZE(3)),
    amf-region-id         INTEGER (0..255),
    amf-set-id            INTEGER (0..65535),
    amf-pointer           INTEGER (0..255),
    nr5g-tmsi               OCTET STRING (SIZE(4))
}

END
