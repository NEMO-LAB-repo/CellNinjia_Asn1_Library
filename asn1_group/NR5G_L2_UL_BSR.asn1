NR5G-L2-UL-BSR DEFINITIONS ::= BEGIN

-- S_H --
NR5G-L2-UL-BSR-S-H  ::= SEQUENCE
{
    version                 INTEGER (0..4294967295),

    skip0                   BIT STRING (SIZE(12)),
    lcid-prio-bitmask       INTEGER (0..65535),
    num-tti               INTEGER (0..15)
}

--TTI--
NR5G-L2-UL-BSR-TTI ::= SEQUENCE
{
    sys-time            Sys-Time,

    carrier-id            INTEGER (0..15),
    harq-id              INTEGER (0..15),

    skip1                  BIT STRING (SIZE(8)),
    num-lcid            INTEGER (0..15),
    lcg-bitmask           INTEGER (0..255),
    bsr-length           INTEGER (0..15),
    bsr-type             BSR-Type,
    bsr-trigger-reason   BSR-Trigger-Reason,

    skip2                  OCTET STRING (SIZE(3))

    -- LCID -- 
    -- skip -- 
    -- BSR MCE Buffer -- 
}
Sys-Time ::= SEQUENCE
{
    slot-number            INTEGER (0..255),
    skip0                  BIT STRING (SIZE(14)),
    fn                   INTEGER (0..1023)
}
BSR-Type ::=ENUMERATED
{
    unknown (0),
    short-bsr (1),
    long-bsr (2),
    unknown3 (3),
    unknown4 (4)
}
BSR-Trigger-Reason ::= ENUMERATED
{
    unknown (0),
    t-periodic-expiry-bsr (1),
    unknown2 (2),
    unknown3 (3),
    high-data-arrival (4),
    t-periodic-expiry-bsr-or-high-data-arrival (5),
    unknown6 (6),
    unknown7 (7),
    unknown8 (8),
    unknown9 (9),
    unknown10 (10),
    unknown11 (11),
    unknown12 (12),
    unknown13 (13),
    unknown14 (14),
    unknown15 (15),
    unknown16 (16)
}

END
