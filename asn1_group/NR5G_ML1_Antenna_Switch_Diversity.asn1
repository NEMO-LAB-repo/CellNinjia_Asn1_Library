NR5G-ML1-Antenna-Switch-Diversity-v131074 DEFINITIONS ::=BEGIN

NR5G-ML1-Antenna-Switch-Diversity-v131074-S-H ::=SEQUENCE
{
    version                 INTEGER (0..4294967295),
    skip0                   BIT STRING (SIZE(2)),
    subfn                 INTEGER (0..15),
    sfn                INTEGER (0..1023),

    slot                 INTEGER (0..255),
    skip1                   BIT STRING (SIZE(5)),
    scs                SCS,

    skip2              OCTET STRING (SIZE(4)),

    dl-action-time       DL-Action-Time,
    skip3                OCTET STRING (SIZE(12))
}

DL-Action-Time ::= SEQUENCE
{
    skip0                  BIT STRING (SIZE(2)),
    subfn                INTEGER (0..15),
    sfn                 INTEGER (0..1023),
    slot                INTEGER (0..255),
    skip1                  BIT STRING (SIZE(5)),
    scs                 SCS
}
SCS ::= ENUMERATED
{
    scs15kHz (0),
    scs30kHz (1),
    scs60kHz (2),
    scs120kHz (3),
    scs240kHz (4)
}

--CC data--
NR5G-ML1-Antenna-Switch-Diversity-v131074-CC-Data ::= SEQUENCE
{
    skip0                  BIT STRING (SIZE(3)),
    switch-reason          SWITCH-Reason,
    switch-mode            SWITCH-Mode,
    skip1                  BIT STRING (SIZE(6)),
    switch-denial-reason SWITCH-Denial-Reason,
    skip2                  BIT STRING (SIZE(17)),

    chain-data-0         CHAIN-DATA,
    chain-data-1         CHAIN-DATA,
    chain-data-2         CHAIN-DATA,
    chain-data-3         CHAIN-DATA,
    chain-data-4         CHAIN-DATA,
    chain-data-5         CHAIN-DATA
}

SWITCH-Reason ::= ENUMERATED
{
    unset (0),
    unknown1 (1),
    unknown2 (2),
    unknown3 (3),
    normal (4),
    edge (5)
}

SWITCH-Mode ::= ENUMERATED
{
    invalid (0),
    normal (1),
    edge (2)
}

SWITCH-Denial-Reason ::= ENUMERATED
{
    none (0),
    same-config-request (1)
}

CHAIN-DATA ::= SEQUENCE
{
    skip0                  OCTET STRING (SIZE(20)),
    old-antenna-id        INTEGER (0..255),
    skip1                 OCTET STRING (SIZE(1)),
    switch-type           INTEGER (0..255),
    new-antenna-id        INTEGER (0..255)
}

END
