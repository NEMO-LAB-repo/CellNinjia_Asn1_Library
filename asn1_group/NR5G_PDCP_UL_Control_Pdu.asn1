NR5G-PDCP-UL-Control-Pdu DEFINITIONS ::= BEGIN


NR5G-PDCP-UL-Control-Pdu-S-H  ::= SEQUENCE
{
    version                 INTEGER (0..4294967295),
    num-control-pdu      INTEGER (0..255),
    skip0                   OCTET STRING (SIZE(3))
}

-- PDU -- 
NR5G-PDCP-UL-Control-Pdu-Content ::= SEQUENCE
{
    skip0                   BIT STRING (SIZE(7)),
    pad-size               INTEGER (0..3),
    size                 INTEGER (0..1023),
    rb-type              RB-Type,
    rn-mode              RB-Mode,
    pdcp-sn-length       PDCP-SN-Length,
    rb-id               INTEGER (0..63),

    sys-time            Sys-Time,
    skip1               OCTET STRING (SIZE(1)),
    fmc                 INTEGER (0..4294967295),
    skip2               OCTET STRING (SIZE(3))
}
RB-Type ::= ENUMERATED
{
    unknown (0),
    srb (1),
    drb (2),
    unknown3 (3)
}
RB-Mode ::= ENUMERATED
{
    unknown (0),
    am (1),
    unknown2 (2),
    unknown3 (3)
}
PDCP-SN-Length ::= ENUMERATED
{
    unknown (0),
    unknown1 (1),
    sn-18 (2),
    unknown3 (3),
    unknown4 (4),
    unknown5 (5),
    unknown6 (6),
    unknown7 (7)
}
Sys-Time ::= SEQUENCE
{
    slot-number            INTEGER (0..255),
    skip0                  BIT STRING (SIZE(14)),
    fn                   INTEGER (0..1023)
}
END
