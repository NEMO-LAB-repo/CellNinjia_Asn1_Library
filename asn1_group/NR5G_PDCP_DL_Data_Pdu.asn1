NR5G-PDCP-DL-Data-PDU DEFINITIONS ::=BEGIN

NR5G-PDCP-DL-Data-PDU-S-H ::=SEQUENCE
{
    version                     INTEGER(0..4294967295),
    number-of-meta              INTEGER(0..65535),
    number-of-rb                INTEGER(0..65535),
    log-count                   INTEGER(0..65535)
}

NR5G-PDCP-DL-Data-PDU-PDCP-State ::=SEQUENCE
{
    rb-cfg-index                INTEGER(0..4294967295),
    rx-deliv                    INTEGER(0..4294967295),
    rx-next                     INTEGER(0..4294967295),
    next-count                  INTEGER(0..4294967295)
}

NR5G-PDCP-DL-Data-PDU-Meta-Log-Buffer ::=SEQUENCE
{
    slot                        INTEGER(0..65535),
    frame                       INTEGER(0..65535),
    rx-timetick-raw             INTEGER(0..4294967295),
    key-index                   INTEGER(0..4294967295),

    skip0                       BIT STRING(SIZE(7)),
    rlc-path                    Rlc-Path,

    skip1                       BIT STRING(SIZE(30)),
    route-status                Route-Status,

    ip-packet-header-0          INTEGER(0..255),
    ip-packet-header-1          INTEGER(0..255),

    start-count                 INTEGER(0..4294967295),
    end-count                   INTEGER(0..4294967295),
    rlc-end-sn                  INTEGER(0..4294967295),
    num-ip-pkts                 INTEGER(0..4294967295),
    number-ip-bytes             INTEGER(0..4294967295)
}

Rlc-Path ::=ENUMERATED
{
    unknown0                    (0),
    nr                          (1)
}

Route-Status ::=ENUMERATED
{
    unknown0                    (0),
    deliv-direct                (1),
    deliv-reord-exp             (2)
}


END
